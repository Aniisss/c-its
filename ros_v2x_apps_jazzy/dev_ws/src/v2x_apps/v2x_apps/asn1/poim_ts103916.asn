-- POIM ASN.1 Schema
-- Based on ETSI TS 103 916 V2.1.1
-- "Intelligent Transport Systems (ITS); ITS application layer;
--  Point of Interest Message for Parking Availability"
--
-- This schema is used by the poim_provider ROS 2 node to encode
-- Point of Interest Messages (POIM) for transmission via the BTP service.
--
-- Encoding rule: UPER (Unaligned Packed Encoding Rules)
-- as used throughout ETSI ITS application-layer standards.
--
-- IMPORTANT: Verify all type definitions, constraints, and the message ID /
-- BTP-B port number against the published ETSI TS 103 916 V2.1.1 before
-- deploying in a production environment. The authoritative ASN.1 files are
-- available at https://forge.etsi.org/rep/ITS/asn1/poim_ts103916

POIM-PDU-Descriptions DEFINITIONS AUTOMATIC TAGS ::= BEGIN

-- ITS PDU Header
-- Defined in ETSI TS 102 894-2 (Common Data Dictionary)
-- Included here directly to keep this module self-contained.

ItsPduHeader ::= SEQUENCE {
    protocolVersion    INTEGER (0..255),
    messageID          INTEGER (0..255),
    stationID          INTEGER (0..4294967295)
}

-- Generation delta time
-- Unit: milliseconds modulo 65536 (wraps around)
-- Defined in ETSI TS 102 894-2

GenerationDeltaTime ::= INTEGER (0..65535)

-- Geographic position types (from ETSI TS 102 894-2)

-- Latitude in 1/10 micro-degrees, range 90 degrees
-- Unavailable value: 900000001
Latitude ::= INTEGER (-900000000..900000001)

-- Longitude in 1/10 micro-degrees, range 180 degrees
-- Unavailable value: 1800000001
Longitude ::= INTEGER (-1800000000..1800000001)

-- Semi-axis length of position confidence ellipse in cm
-- Unavailable: 4094, OutOfRange: 4095
SemiAxisLength ::= INTEGER (0..4095)

-- Confidence ellipse of the reference position
PosConfidenceEllipse ::= SEQUENCE {
    semiMajorConfidence    SemiAxisLength,
    semiMinorConfidence    SemiAxisLength,
    semiMajorOrientation   INTEGER (0..3601)
}

-- Altitude value in cm above the WGS-84 reference ellipsoid
-- Range: -100000 (-1000 m) to 800000 (8000 m)
-- Unavailable: 800001
AltitudeValue ::= INTEGER (-100000..800001)

-- Altitude measurement confidence (16 levels per ETSI TS 102 894-2)
AltitudeConfidence ::= ENUMERATED {
    alt000-01,
    alt000-02,
    alt000-05,
    alt000-10,
    alt000-20,
    alt000-50,
    alt001-00,
    alt002-00,
    alt005-00,
    alt010-00,
    alt020-00,
    alt050-00,
    alt100-00,
    alt200-00,
    outOfRange,
    unavailable
}

Altitude ::= SEQUENCE {
    altitudeValue         AltitudeValue,
    altitudeConfidence    AltitudeConfidence
}

-- Reference position: WGS-84 latitude/longitude + altitude + confidence
ReferencePosition ::= SEQUENCE {
    latitude                    Latitude,
    longitude                   Longitude,
    positionConfidenceEllipse   PosConfidenceEllipse,
    altitude                    Altitude
}

-- POIM-specific types (ETSI TS 103 916 V2.1.1)

-- Unique identifier of a Point of Interest
PoiId ::= INTEGER (0..65535)

-- Number of available parking spaces at the facility
ParkingSpacesAvailable ::= INTEGER (0..65535)

-- Total number of parking spaces at the facility (static capacity)
ParkingSpacesTotal ::= INTEGER (0..65535)

-- Number of currently occupied parking spaces
ParkingSpacesOccupied ::= INTEGER (0..65535)

-- Duration in seconds for which the information is valid
ValidityDuration ::= INTEGER (0..86400)

-- Parking Facility Container
-- Carries real-time parking availability data for a single parking facility.
-- Defined in ETSI TS 103 916 (Parking Availability container)

ParkingFacilityContainer ::= SEQUENCE {
    poiId                    PoiId,
    referencePosition        ReferencePosition,
    parkingSpacesAvailable   ParkingSpacesAvailable,
    parkingSpacesTotal       ParkingSpacesTotal    OPTIONAL,
    parkingSpacesOccupied    ParkingSpacesOccupied OPTIONAL,
    validityDuration         ValidityDuration       OPTIONAL
}

-- POI Container: CHOICE to allow future extension with additional
-- service types (EV charging, fuel stations, etc.).
-- Currently only the parking-facility variant is defined.

PoiContainer ::= CHOICE {
    parkingFacility    ParkingFacilityContainer
}

-- A POIM carries between 1 and 8 POI containers
PoiContainers ::= SEQUENCE (SIZE(1..8)) OF PoiContainer

-- POIM body

PoiBody ::= SEQUENCE {
    generationDeltaTime    GenerationDeltaTime,
    poiContainers          PoiContainers
}

-- Top-level POIM PDU
-- BTP-B destination port: see ETSI TS 103 916 Table 1 (Communication Profile)
-- ItsPduHeader.messageID: see ETSI TS 102 894-2

POIM ::= SEQUENCE {
    header    ItsPduHeader,
    poim      PoiBody
}

END
